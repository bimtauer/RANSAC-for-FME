FME workspace FME_test.fmw

Parameters:
- SourceDataset_LAS = $(FME_MF_DIR)Data\poles.las   # Source ASPRS LAS File(s)

Readers:
- LAS_1: LAS from $(SourceDataset_LAS)

LAS (reader LAS_1)
    -> PointCloudThinner
PointCloudThinner
    MAX_NUM_POINTS = 100
    THINNED -> PointCloudCoercer
PointCloudCoercer
    ACCUM_ATTRS_NAME = Yes
    CONVERT_TO_DISPLAY = Individual Points
    PART_NUMBER_ATTR_NAME = _part_number
    POINT_COMPONENTS_PRESERVE_DISPLAY = Attributes
    COERCED -> PythonCaller
PythonCaller
    PYTHONSOURCE:
      import fme
      import fmeobjects
      import numpy as np
      import pcl
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              self.points = []
              pass
          def input(self,feature):
              p = feature.getAllCoordinates()
              self.points.append([p[0][0], p[0][1], p[0][2]])
              pass
              #self.pyoutput(feature)
          def close(self):
              array = np.array(self.points)
              print(array)
              pc = pcl.PointCloud()
              #pc.from_array(array)
              pass
    PYTHONSYMBOL = FeatureProcessor
